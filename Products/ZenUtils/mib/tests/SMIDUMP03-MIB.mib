SMIDUMP03-MIB DEFINITIONS ::= BEGIN

IMPORTS
    MODULE-IDENTITY, snmpModules
        FROM SNMPv2-SMI;

smidump03 MODULE-IDENTITY
    LAST-UPDATED "201805030000Z"
    ORGANIZATION "Zenoss Inc."
    CONTACT-INFO "EMail: dev@zenoss.com"
    DESCRIPTION  "This is a test MIB module."
    REVISION     "201805030000Z"
    DESCRIPTION
            "Initial version."

    ::= { snmpModules 19 }

END
